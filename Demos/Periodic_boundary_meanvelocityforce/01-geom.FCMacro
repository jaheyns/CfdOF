import FreeCAD
import PartDesignGui
import os

# Gui.runCommand('Std_DlgMacroRecord',0)
### Begin command Std_Open
FreeCAD.openDocument(os.path.join(os.path.dirname(__file__), "periodic_boundary_meanvelocityforce.FCStd"))
# App.setActiveDocument("periodic_boundary_meanvelocityforce")
# App.ActiveDocument=App.getDocument("periodic_boundary_meanvelocityforce")
# Gui.ActiveDocument=Gui.getDocument("periodic_boundary_meanvelocityforce")
### End command Std_Open
App.ActiveDocument.recompute()
