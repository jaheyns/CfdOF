from os import path
from CfdOF.CfdTools import executeMacro
dir = path.dirname(__file__)
executeMacro(path.join(dir, '01-geom.FCMacro'))
executeMacro(path.join(dir, '02-analysis.FCMacro'))
executeMacro(path.join(dir, '03-mesh.FCMacro'))
executeMacro(path.join(dir, '04-boundry_conditions.FCMacro'))
executeMacro(path.join(dir, '05-mean_velocity_force.FCMacro'))
Gui.SendMsgToActiveView("ViewFit")
