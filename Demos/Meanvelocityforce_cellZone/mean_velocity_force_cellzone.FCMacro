# -*- coding: utf-8 -*-
# Pre-import CfdOF modules so that proxy classes are available when FreeCAD
# restores the document objects from the FCStd file.
import os
from CfdOF import CfdAnalysis
from CfdOF.Solve import CfdSolverFoam
from CfdOF.Solve import CfdPhysicsSelection
from CfdOF.Solve import CfdFluidMaterial
from CfdOF.Solve import CfdInitialiseFlowField
from CfdOF.Solve import CfdFluidBoundary
from CfdOF.Solve import CfdMeanVelocityForce
from CfdOF.Solve import CfdZone
from CfdOF.Mesh import CfdMesh
from CfdOF import CfdTools

doc = FreeCAD.open(os.path.join(os.path.dirname(__file__), "mean_velocity_force_cellzone.FCStd"))
FreeCAD.setActiveDocument(doc.Name)

# Ensure the CfdAnalysis is set as active
analysis = CfdTools.getActiveAnalysis()
if analysis is None:
    for obj in FreeCAD.ActiveDocument.Objects:
        if hasattr(obj, 'IsActiveAnalysis') and hasattr(obj, 'OutputPath'):
            obj.IsActiveAnalysis = True
            break
