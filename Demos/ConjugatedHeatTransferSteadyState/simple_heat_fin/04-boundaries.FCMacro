from CfdOF import CfdTools
from CfdOF.Solve import CfdFluidBoundary

def add_boundary(label, boundary_type, subtype, thermal_type, faces,
                 temperature="293 K", velocity=(0, 0, 0)):
    boundary = CfdFluidBoundary.makeCfdFluidBoundary()
    CfdTools.getActiveAnalysis().addObject(boundary)
    boundary.Label = label
    boundary.BoundaryType = boundary_type
    boundary.BoundarySubType = subtype
    boundary.ThermalBoundaryType = thermal_type
    boundary.Temperature = temperature
    boundary.Ux = "{} mm/s".format(velocity[0])
    boundary.Uy = "{} mm/s".format(velocity[1])
    boundary.Uz = "{} mm/s".format(velocity[2])
    boundary.TurbulenceIntensityPercentage = 1.0
    boundary.TurbulenceLengthScale = "100 mm"
    boundary.ShapeRefs = [(App.ActiveDocument.BooleanFragments, tuple(faces))]
    return boundary

add_boundary("wall001", "wall", "fixedWall", "zeroGradient",
             ("Face4", "Face1", "Face3", "Face10"))
add_boundary("heatsource001", "wall", "fixedWall", "fixedValue",
             ("Face12",), "393 K")
add_boundary("inlet", "inlet", "uniformVelocityInlet", "fixedValue",
             ("Face2",), velocity=(0, 100, 0))
add_boundary("outlet", "outlet", "staticPressureOutlet", "fixedValue",
             ("Face5",))
App.ActiveDocument.recompute()
