import FreeCAD as App

from CfdOF import CfdTools
from CfdOF.Mesh import CfdMesh


def add_mesh(name, part, case_name, length):
    CfdMesh.makeCfdMesh(name)
    mesh = App.ActiveDocument.ActiveObject
    CfdTools.getActiveAnalysis().addObject(mesh)
    mesh.Part = part
    mesh.CaseName = case_name
    mesh.CharacteristicLengthMax = length
    mesh.MeshUtility = "gmsh"
    mesh.ElementDimension = "3D"
    mesh.CellsBetweenLevels = 3
    mesh.EdgeRefinement = 1.0
    mesh.PointInMesh = {"x": "0 m", "y": "0 m", "z": "0 m"}
    mesh.NumberOfProcesses = 1
    return mesh


add_mesh(
    "Fluid_Mesh",
    App.ActiveDocument.FluidRegion,
    "meshCaseSimpleHeatFinNccFluid",
    "5 mm",
)
add_mesh(
    "Solid_Mesh",
    App.ActiveDocument.SolidRegion,
    "meshCaseSimpleHeatFinNccSolid",
    "3 mm",
)

App.ActiveDocument.recompute()
