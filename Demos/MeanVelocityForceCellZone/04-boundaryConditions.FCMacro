from CfdOF.Solve import CfdFluidBoundary
from CfdOF import CfdTools

CfdTools.getActiveAnalysis().addObject(CfdFluidBoundary.makeCfdFluidBoundary())
App.ActiveDocument.CfdFluidBoundary.Label = 'wall'
App.ActiveDocument.CfdFluidBoundary.RotationAxis = App.Vector (0.0, 0.0, 0.0)
App.ActiveDocument.CfdFluidBoundary.PeriodicCentreOfRotationAxis = App.Vector (0.0, 0.0, 0.0)
FreeCAD.ActiveDocument.CfdFluidBoundary.ShapeRefs = [
(FreeCAD.ActiveDocument.getObject('Box'), ('Face3', 'Face2', 'Face6', 'Face1', 'Face5', 'Face4'))]
FreeCAD.ActiveDocument.recompute()
