import FreeCAD
import PartDesignGui
import Part

# make a new document
App.newDocument()

# make a cube that will be the fluid domain
App.ActiveDocument.addObject("Part::Box","Box")
App.ActiveDocument.ActiveObject.Label = "Cube"
FreeCAD.ActiveDocument.Box.Length = '100 mm'
FreeCAD.ActiveDocument.Box.Width = '100 mm'
FreeCAD.ActiveDocument.Box.Height = '100 mm'

# make the 3 cylinders for the mean velocity zones
App.ActiveDocument.addObject("Part::Cylinder","Cylinder")
App.ActiveDocument.ActiveObject.Label = "Cylinder"
FreeCAD.ActiveDocument.Cylinder.Placement = App.Placement(App.Vector(75,75,47),App.Rotation(App.Vector(0,1,0),90))
FreeCAD.ActiveDocument.Cylinder.Radius = '10 mm'
FreeCAD.ActiveDocument.Cylinder.Height = '4 mm'

App.ActiveDocument.addObject("Part::Cylinder","Cylinder")
App.ActiveDocument.ActiveObject.Label = "Cylinder"
FreeCAD.ActiveDocument.Cylinder001.Placement = App.Placement(App.Vector(21,51,71),App.Rotation(App.Vector(1,0,0),270))
FreeCAD.ActiveDocument.Cylinder001.Radius = '10 mm'
FreeCAD.ActiveDocument.Cylinder001.Height = '4 mm'

App.ActiveDocument.addObject("Part::Cylinder","Cylinder")
App.ActiveDocument.ActiveObject.Label = "Cylinder"
FreeCAD.ActiveDocument.Cylinder002.Placement = App.Placement(App.Vector(45,24,47),App.Rotation(App.Vector(0,0,1),0))
FreeCAD.ActiveDocument.Cylinder002.Radius = '10 mm'
FreeCAD.ActiveDocument.Cylinder002.Height = '4 mm'
App.ActiveDocument.recompute()
