# -*- coding: utf-8 -*-

import FreeCAD
import PartDesignGui
import Part

App.newDocument()
App.ActiveDocument.addObject("Part::Cylinder","Cylinder")
App.ActiveDocument.Cylinder.Label = "Cylinder"
App.ActiveDocument.recompute()
App.ActiveDocument.getObject('Cylinder').Radius = '10 mm'
App.ActiveDocument.getObject('Cylinder').Height = '20 mm'

App.ActiveDocument.addObject("Part::Box","Box")
App.ActiveDocument.Box.Label = "Cube"
App.ActiveDocument.recompute()
App.ActiveDocument.getObject('Box').Length = '30 mm'
App.ActiveDocument.getObject('Box').Width = '2 mm'
App.ActiveDocument.getObject('Box').Height = '15 mm'
App.ActiveDocument.getObject('Box').Placement = App.Placement(App.Vector(0,0,2.5),App.Rotation(App.Vector(0,0,1),0))

App.ActiveDocument.addObject("Part::Box","Box")
App.ActiveDocument.Box001.Label = "Cube"
App.ActiveDocument.recompute()
App.ActiveDocument.getObject('Box001').Length = '2 mm'
App.ActiveDocument.getObject('Box001').Width = '30 mm'
App.ActiveDocument.getObject('Box001').Height = '15 mm'
App.ActiveDocument.getObject('Box001').Placement = App.Placement(App.Vector(0,0,2.5),App.Rotation(App.Vector(0,0,1),0))

from BOPTools import BOPFeatures
bp = BOPFeatures.BOPFeatures(App.activeDocument())
bp.make_multi_fuse(["Box", "Box001", ])
App.ActiveDocument.recompute()
__doc__=App.ActiveDocument
__doc__.addObject("Part::Mirroring")
__doc__.ActiveObject.Source=__doc__.getObject("Fusion")
__doc__.ActiveObject.Label=u"Fusion (Mirror #1)"
__doc__.ActiveObject.Normal=(0,1,0)
__doc__.ActiveObject.Base=(0,0,0)
__doc__.ActiveObject.MirrorPlane=()
del __doc__
bp = BOPFeatures.BOPFeatures(App.activeDocument())
bp.make_multi_fuse(["Part__Mirroring", "Fusion", ])
App.ActiveDocument.recompute()
__doc__=App.ActiveDocument
__doc__.addObject("Part::Mirroring")
__doc__.ActiveObject.Source=__doc__.getObject("Fusion001")
__doc__.ActiveObject.Label=u"Fusion001 (Mirror #2)"
__doc__.ActiveObject.Normal=(1,0,0)
__doc__.ActiveObject.Base=(0,0,0)
__doc__.ActiveObject.MirrorPlane=()
del __doc__
bp = BOPFeatures.BOPFeatures(App.activeDocument())
bp.make_multi_fuse(["Part__Mirroring001", "Fusion001", "Cylinder", ])
App.ActiveDocument.recompute()
App.ActiveDocument.addObject("Part::Cylinder","Cylinder")
App.ActiveDocument.Cylinder001.Label = "Cylinder"
App.ActiveDocument.recompute()
App.ActiveDocument.getObject('Cylinder001').Radius = '35 mm'
App.ActiveDocument.getObject('Cylinder001').Height = '30 mm'
App.ActiveDocument.getObject('Cylinder001').Placement = App.Placement(App.Vector(0,0,-5),App.Rotation(App.Vector(0,0,1),0))

App.ActiveDocument.addObject("Part::Cylinder","Cylinder")
App.ActiveDocument.Cylinder002.Label = "Cylinder"
App.ActiveDocument.recompute()
App.ActiveDocument.getObject('Cylinder002').Radius = '40 mm'
App.ActiveDocument.getObject('Cylinder002').Height = '40 mm'
App.ActiveDocument.getObject('Cylinder002').Placement = App.Placement(App.Vector(0,0,-10),App.Rotation(App.Vector(0,0,1),0))

bp = BOPFeatures.BOPFeatures(App.activeDocument())
bp.make_cut(["Cylinder002", "Fusion002", ])
App.ActiveDocument.recompute()
Gui.SendMsgToActiveView("ViewFit")
