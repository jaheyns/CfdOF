# -*- coding: utf-8 -*-

import FreeCAD
import PartDesignGui
import Part

App.newDocument()
App.ActiveDocument.addObject("Part::Cylinder","Cylinder")
App.ActiveDocument.ActiveObject.Label = "Cylinder"
App.ActiveDocument.recompute()
FreeCAD.getDocument('Unnamed').getObject('Cylinder').Radius = '10 mm'
FreeCAD.getDocument('Unnamed').getObject('Cylinder').Height = '20 mm'

App.ActiveDocument.addObject("Part::Box","Box")
App.ActiveDocument.ActiveObject.Label = "Cube"
App.ActiveDocument.recompute()
FreeCAD.getDocument('Unnamed').getObject('Box').Length = '30 mm'
FreeCAD.getDocument('Unnamed').getObject('Box').Width = '2 mm'
FreeCAD.getDocument('Unnamed').getObject('Box').Height = '15 mm'
FreeCAD.getDocument('Unnamed').getObject('Box').Placement = App.Placement(App.Vector(0,0,2.5),App.Rotation(App.Vector(0,0,1),0))

App.ActiveDocument.addObject("Part::Box","Box")
App.ActiveDocument.ActiveObject.Label = "Cube"
App.ActiveDocument.recompute()
FreeCAD.getDocument('Unnamed').getObject('Box001').Length = '2 mm'
FreeCAD.getDocument('Unnamed').getObject('Box001').Width = '30 mm'
FreeCAD.getDocument('Unnamed').getObject('Box001').Height = '15 mm'
FreeCAD.getDocument('Unnamed').getObject('Box001').Placement = App.Placement(App.Vector(0,0,2.5),App.Rotation(App.Vector(0,0,1),0))

from BOPTools import BOPFeatures
bp = BOPFeatures.BOPFeatures(App.activeDocument())
bp.make_multi_fuse(["Box", "Box001", ])
App.ActiveDocument.recompute()
__doc__=FreeCAD.getDocument("Unnamed")
__doc__.addObject("Part::Mirroring")
__doc__.ActiveObject.Source=__doc__.getObject("Fusion")
__doc__.ActiveObject.Label=u"Fusion (Mirror #1)"
__doc__.ActiveObject.Normal=(0,1,0)
__doc__.ActiveObject.Base=(0,0,0)
__doc__.ActiveObject.MirrorPlane=()
del __doc__
bp = BOPFeatures.BOPFeatures(App.activeDocument())
bp.make_multi_fuse(["Part__Mirroring", "Fusion", ])
App.ActiveDocument.recompute()
__doc__=FreeCAD.getDocument("Unnamed")
__doc__.addObject("Part::Mirroring")
__doc__.ActiveObject.Source=__doc__.getObject("Fusion001")
__doc__.ActiveObject.Label=u"Fusion001 (Mirror #2)"
__doc__.ActiveObject.Normal=(1,0,0)
__doc__.ActiveObject.Base=(0,0,0)
__doc__.ActiveObject.MirrorPlane=()
del __doc__
bp = BOPFeatures.BOPFeatures(App.activeDocument())
bp.make_multi_fuse(["Part__Mirroring001", "Fusion001", "Cylinder", ])
App.ActiveDocument.recompute()
App.ActiveDocument.addObject("Part::Cylinder","Cylinder")
App.ActiveDocument.ActiveObject.Label = "Cylinder"
App.ActiveDocument.recompute()
FreeCAD.getDocument('Unnamed').getObject('Cylinder001').Radius = '35 mm'
FreeCAD.getDocument('Unnamed').getObject('Cylinder001').Height = '30 mm'
FreeCAD.getDocument('Unnamed').getObject('Cylinder001').Placement = App.Placement(App.Vector(0,0,-5),App.Rotation(App.Vector(0,0,1),0))

App.ActiveDocument.addObject("Part::Cylinder","Cylinder")
App.ActiveDocument.ActiveObject.Label = "Cylinder"
App.ActiveDocument.recompute()
FreeCAD.getDocument('Unnamed').getObject('Cylinder002').Radius = '40 mm'
FreeCAD.getDocument('Unnamed').getObject('Cylinder002').Height = '40 mm'
FreeCAD.getDocument('Unnamed').getObject('Cylinder002').Placement = App.Placement(App.Vector(0,0,-10),App.Rotation(App.Vector(0,0,1),0))

bp = BOPFeatures.BOPFeatures(App.activeDocument())
bp.make_cut(["Cylinder002", "Fusion002", ])
App.ActiveDocument.recompute()
from CfdOF import CfdAnalysis
from CfdOF import CfdTools
analysis = CfdAnalysis.makeCfdAnalysis('CfdAnalysis')
CfdTools.setActiveAnalysis(analysis)
from CfdOF.Solve import CfdPhysicsSelection
analysis.addObject(CfdPhysicsSelection.makeCfdPhysicsSelection())
from CfdOF.Solve import CfdFluidMaterial
analysis.addObject(CfdFluidMaterial.makeCfdFluidMaterial('FluidProperties'))
from CfdOF.Solve import CfdInitialiseFlowField
analysis.addObject(CfdInitialiseFlowField.makeCfdInitialFlowField())
from CfdOF.Solve import CfdSolverFoam
analysis.addObject(CfdSolverFoam.makeCfdSolverFoam())
from CfdOF.Solve import CfdFluidBoundary
from CfdOF import CfdTools
CfdTools.getActiveAnalysis().addObject(CfdFluidBoundary.makeCfdFluidBoundary())
App.ActiveDocument.CfdFluidBoundary.Label = 'inlet'
FreeCAD.ActiveDocument.CfdFluidBoundary.BoundaryType = 'inlet'
FreeCAD.ActiveDocument.CfdFluidBoundary.BoundarySubType = 'uniformVelocityInlet'
App.ActiveDocument.CfdFluidBoundary.Uz = '-1000.0 mm/s'
App.ActiveDocument.CfdFluidBoundary.Temperature = '290.0 K'
FreeCAD.ActiveDocument.CfdFluidBoundary.ShapeRefs = [
(FreeCAD.ActiveDocument.getObject('Cut'), ('Face3',))]
FreeCAD.ActiveDocument.recompute()
CfdTools.getActiveAnalysis().addObject(CfdFluidBoundary.makeCfdFluidBoundary())
App.ActiveDocument.CfdFluidBoundary001.Label = 'outlet'
FreeCAD.ActiveDocument.CfdFluidBoundary001.BoundaryType = 'outlet'
FreeCAD.ActiveDocument.CfdFluidBoundary001.BoundarySubType = 'staticPressureOutlet'
App.ActiveDocument.CfdFluidBoundary001.Temperature = '290.0 K'
FreeCAD.ActiveDocument.CfdFluidBoundary001.ShapeRefs = [
(FreeCAD.ActiveDocument.getObject('Cut'), ('Face2',))]
FreeCAD.ActiveDocument.recompute()
CfdTools.getActiveAnalysis().addObject(CfdFluidBoundary.makeCfdFluidBoundary())
App.ActiveDocument.CfdFluidBoundary002.Label = 'wall'
App.ActiveDocument.CfdFluidBoundary002.Temperature = '290.0 K'
FreeCAD.ActiveDocument.CfdFluidBoundary002.ShapeRefs = [
(FreeCAD.ActiveDocument.getObject('Cut'), ('Face1',))]
FreeCAD.ActiveDocument.recompute()
CfdTools.getActiveAnalysis().addObject(CfdFluidBoundary.makeCfdFluidBoundary())
App.ActiveDocument.CfdFluidBoundary003.Label = 'wall'
App.ActiveDocument.CfdFluidBoundary003.Temperature = '290.0 K'
App.ActiveDocument.CfdFluidBoundary003.DefaultBoundary = True
FreeCAD.ActiveDocument.recompute()
App.ActiveDocument.PhysicsModel.Time = 'Transient'
App.ActiveDocument.PhysicsModel.gy = '-9800.0 mm/s^2'
from CfdOF.Mesh import CfdMesh
CfdMesh.makeCfdMesh('Cut_Mesh')
App.ActiveDocument.ActiveObject.Part = App.ActiveDocument.Cut
CfdTools.getActiveAnalysis().addObject(App.ActiveDocument.ActiveObject)
App.ActiveDocument.Cut_Mesh.CharacteristicLengthMax = '2.0 mm'
App.ActiveDocument.Cut_Mesh.MeshUtility = 'snappyHexMesh'
App.ActiveDocument.Cut_Mesh.PointInMesh = {'x': '37.0 mm', 'y': '0.0 mm', 'z': '0.0 mm'}

from CfdOF.Mesh import CfdMeshRefinement
CfdMeshRefinement.makeCfdMeshRefinement(App.ActiveDocument.Cut_Mesh)
FreeCAD.ActiveDocument.MeshRefinement.ShapeRefs = [
(FreeCAD.ActiveDocument.getObject('Cylinder001'), ('',))]
App.ActiveDocument.MeshRefinement.MovingMeshRegion = True
App.ActiveDocument.MeshRefinement.MMRModelRPM = '19.00 '
App.ActiveDocument.MeshRefinement.MMRModelAxis = App.Vector (0.0, 0.0, 1.0)
FreeCAD.ActiveDocument.recompute()
App.ActiveDocument.InitialiseFields.Temperature = '290.0 K'
FreeCAD.ActiveDocument.InitialiseFields.BoundaryP = FreeCAD.ActiveDocument.CfdFluidBoundary001
App.activeDocument().recompute(None,True,True)
Gui.SendMsgToActiveView("ViewFit")
