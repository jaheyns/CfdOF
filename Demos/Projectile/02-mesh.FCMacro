import FreeCAD
from CfdOF import CfdAnalysis
from CfdOF import CfdTools
from CfdOF.Solve import CfdPhysicsSelection
from CfdOF.Solve import CfdFluidMaterial
from CfdOF.Solve import CfdInitialiseFlowField
from CfdOF.Solve import CfdSolverFoam
from CfdOF.Mesh import CfdMesh
from CfdOF.Mesh import CfdMeshRefinement

analysis = CfdAnalysis.makeCfdAnalysis('CfdAnalysis')
CfdTools.setActiveAnalysis(analysis)
analysis.addObject(CfdPhysicsSelection.makeCfdPhysicsSelection())
analysis.addObject(CfdFluidMaterial.makeCfdFluidMaterial('FluidProperties'))
analysis.addObject(CfdInitialiseFlowField.makeCfdInitialFlowField())
analysis.addObject(CfdSolverFoam.makeCfdSolverFoam())

obj = FreeCAD.ActiveDocument.PhysicsModel
obj.Time = 'Steady'
obj.Phase = 'Single'
obj.Flow = 'HighMachCompressible'
obj.Turbulence = 'RANS'
obj.TurbulenceModel = 'kOmegaSST'
obj.gx = '0 m/s^2'
obj.gy = '-9,81 m/s^2'
obj.gz = '0 m/s^2'

FreeCAD.ActiveDocument.FluidProperties.Material = {'CardName': 'AirCompressible', 'AuthorAndLicense': '', 'Name': 'Air', 'Type': 'Compressible', 'Description': 'Compressible air properties', 'MolarMass': '0.0289643897748887 kg/mol', 'Cp': '1004.703 J/kg/K', 'SutherlandTemperature': '110.4 K', 'SutherlandRefViscosity': '1.716e-5 kg/m/s', 'SutherlandRefTemperature': '273.15 K'}

FreeCAD.ActiveDocument.getObject('CfdSolver').MaxIterations = 1000

CfdMesh.makeCfdMesh('mesh')
App.ActiveDocument.ActiveObject.Part = App.ActiveDocument.Boolean
CfdTools.getActiveAnalysis().addObject(App.ActiveDocument.ActiveObject)
FreeCAD.ActiveDocument.mesh.CharacteristicLengthMax = '225.0 mm'
FreeCAD.ActiveDocument.mesh.MeshUtility = 'cfMesh'
FreeCAD.ActiveDocument.mesh.ElementDimension = '3D'
FreeCAD.ActiveDocument.mesh.CellsBetweenLevels = 3
FreeCAD.ActiveDocument.mesh.EdgeRefinement = 1.0
FreeCAD.ActiveDocument.mesh.PointInMesh = {'x': '0.0 mm', 'y': '0.0 mm', 'z': '0.0 mm'}

CfdMeshRefinement.makeCfdMeshRefinement(App.ActiveDocument.mesh)
FreeCAD.ActiveDocument.MeshRefinement.RelativeLength = 0.015
FreeCAD.ActiveDocument.MeshRefinement.RefinementThickness = '5 mm'
FreeCAD.ActiveDocument.MeshRefinement.NumberLayers = 10
FreeCAD.ActiveDocument.MeshRefinement.ExpansionRatio = 1.05
FreeCAD.ActiveDocument.MeshRefinement.FirstLayerHeight = '0.0 mm'
FreeCAD.ActiveDocument.MeshRefinement.RegionEdgeRefinement = 1.0
FreeCAD.ActiveDocument.MeshRefinement.Internal = False
FreeCAD.ActiveDocument.MeshRefinement.ShapeRefs = [
(FreeCAD.ActiveDocument.getObject('Body'), ('Face8', 'Face9', 'Face10'))]
FreeCAD.ActiveDocument.recompute()

from CfdOF.Mesh import CfdMeshRefinement
CfdMeshRefinement.makeCfdMeshRefinement(App.ActiveDocument.mesh)
FreeCAD.ActiveDocument.MeshRefinement001.RelativeLength = 0.007
FreeCAD.ActiveDocument.MeshRefinement001.RefinementThickness = '5 mm'
FreeCAD.ActiveDocument.MeshRefinement001.NumberLayers = 10
FreeCAD.ActiveDocument.MeshRefinement001.ExpansionRatio = 1.05
FreeCAD.ActiveDocument.MeshRefinement001.FirstLayerHeight = '0.0 mm'
FreeCAD.ActiveDocument.MeshRefinement001.RegionEdgeRefinement = 1.0
FreeCAD.ActiveDocument.MeshRefinement001.Internal = False
FreeCAD.ActiveDocument.MeshRefinement001.ShapeRefs = [
(FreeCAD.ActiveDocument.getObject('PolarPattern'), ('',))]
FreeCAD.ActiveDocument.recompute()

App.ActiveDocument.addObject("Part::Cylinder","Cylinder")
App.ActiveDocument.ActiveObject.Label = "Cylinder"
App.ActiveDocument.recompute()

App.ActiveDocument.getObject('Cylinder').Radius = '50 mm'
App.ActiveDocument.getObject('Cylinder').Height = '480 mm'
App.ActiveDocument.getObject('Cylinder').Placement = App.Placement(App.Vector(-150,0,0),App.Rotation(App.Vector(0,1,0),90))

CfdMeshRefinement.makeCfdMeshRefinement(App.ActiveDocument.mesh)
FreeCAD.ActiveDocument.MeshRefinement002.RelativeLength = 0.03
FreeCAD.ActiveDocument.MeshRefinement002.Internal = True
FreeCAD.ActiveDocument.MeshRefinement002.ShapeRefs = [
(FreeCAD.ActiveDocument.getObject('Cylinder'), ('Solid1'))]
App.ActiveDocument.Cylinder.Visibility = False
App.ActiveDocument.recompute()

App.ActiveDocument.addObject("Part::Cylinder","Cylinder")
App.ActiveDocument.ActiveObject.Label = "Cylinder"
App.ActiveDocument.recompute()

FreeCAD.ActiveDocument.getObject('Cylinder001').Radius = '100 mm'
FreeCAD.ActiveDocument.getObject('Cylinder001').Height = '650 mm'
FreeCAD.ActiveDocument.getObject('Cylinder001').Placement = App.Placement(App.Vector(-300,0,0),App.Rotation(App.Vector(0,1,0),90))

CfdMeshRefinement.makeCfdMeshRefinement(App.ActiveDocument.mesh)
FreeCAD.ActiveDocument.MeshRefinement003.RelativeLength = 0.06
FreeCAD.ActiveDocument.MeshRefinement003.Internal = True
FreeCAD.ActiveDocument.MeshRefinement003.ShapeRefs = [
(FreeCAD.ActiveDocument.getObject('Cylinder001'), ('Solid1'))]
App.ActiveDocument.Cylinder001.Visibility = False
App.ActiveDocument.recompute()

App.ActiveDocument.addObject("Part::Cylinder","Cylinder")
App.ActiveDocument.ActiveObject.Label = "Cylinder"
App.ActiveDocument.recompute()

App.ActiveDocument.getObject('Cylinder002').Radius = '200 mm'
App.ActiveDocument.getObject('Cylinder002').Height = '900 mm'
App.ActiveDocument.getObject('Cylinder002').Placement = App.Placement(App.Vector(-500,0,0),App.Rotation(App.Vector(0,1,0),90))

CfdMeshRefinement.makeCfdMeshRefinement(App.ActiveDocument.mesh)
FreeCAD.ActiveDocument.MeshRefinement004.RelativeLength = 0.12
FreeCAD.ActiveDocument.MeshRefinement004.Internal = True
FreeCAD.ActiveDocument.MeshRefinement004.ShapeRefs = [
(FreeCAD.ActiveDocument.getObject('Cylinder002'), ('Solid1'))]
App.ActiveDocument.Cylinder002.Visibility = False
App.ActiveDocument.recompute()

App.ActiveDocument.addObject("Part::Cylinder","Cylinder")
App.ActiveDocument.ActiveObject.Label = "Cylinder"
App.ActiveDocument.recompute()

App.ActiveDocument.getObject('Cylinder003').Radius = '400 mm'
App.ActiveDocument.getObject('Cylinder003').Height = '1200 mm'
App.ActiveDocument.getObject('Cylinder003').Placement = App.Placement(App.Vector(-700,0,0),App.Rotation(App.Vector(0,1,0),90))

CfdMeshRefinement.makeCfdMeshRefinement(App.ActiveDocument.mesh)
FreeCAD.ActiveDocument.MeshRefinement005.RelativeLength = 0.12
FreeCAD.ActiveDocument.MeshRefinement005.Internal = True
FreeCAD.ActiveDocument.MeshRefinement005.ShapeRefs = [
(FreeCAD.ActiveDocument.getObject('Cylinder003'), ('Solid1'))]
App.ActiveDocument.Cylinder003.Visibility = False
App.ActiveDocument.recompute()
