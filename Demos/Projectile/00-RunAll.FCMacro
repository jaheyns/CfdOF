from os import path
from CfdOF.CfdTools import executeMacro
dir = path.dirname(__file__)
executeMacro(path.join(dir, '01-geometry.FCMacro'))
executeMacro(path.join(dir, '02-mesh.FCMacro'))
executeMacro(path.join(dir, '03-boundaries.FCMacro'))
executeMacro(path.join(dir, '04-forceCoeffs.FCMacro'))
executeMacro(path.join(dir, '05-adaptiveMesh.FCMacro'))
