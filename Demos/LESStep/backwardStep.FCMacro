# -*- coding: utf-8 -*-

import os
FreeCAD.open(os.path.join(os.path.dirname(__file__), "backwardStep.FCStd"))
Gui.SendMsgToActiveView("ViewFit")

Gui.activateWorkbench("CfdOFWorkbench")
from CfdOF import CfdAnalysis
from CfdOF import CfdTools
analysis = CfdAnalysis.makeCfdAnalysis('CfdAnalysis')
CfdTools.setActiveAnalysis(analysis)
from CfdOF.Solve import CfdPhysicsSelection
analysis.addObject(CfdPhysicsSelection.makeCfdPhysicsSelection())
from CfdOF.Solve import CfdFluidMaterial
analysis.addObject(CfdFluidMaterial.makeCfdFluidMaterial('FluidProperties'))
from CfdOF.Solve import CfdInitialiseFlowField
analysis.addObject(CfdInitialiseFlowField.makeCfdInitialFlowField())
from CfdOF.Solve import CfdSolverFoam
analysis.addObject(CfdSolverFoam.makeCfdSolverFoam())
from CfdOF.Mesh import CfdMesh
CfdMesh.makeCfdMesh('Pad_Mesh')
App.ActiveDocument.ActiveObject.Part = App.ActiveDocument.Pad
CfdTools.getActiveAnalysis().addObject(App.ActiveDocument.ActiveObject)

FreeCAD.ActiveDocument.Pad_Mesh.CharacteristicLengthMax = '0.7 mm'
FreeCAD.ActiveDocument.Pad_Mesh.MeshUtility = 'gmsh'
FreeCAD.ActiveDocument.Pad_Mesh.ConvertToDualMesh = True

obj = FreeCAD.ActiveDocument.PhysicsModel
obj.Time = 'Transient'
obj.Phase = 'Single'
obj.Flow = 'Isothermal'
obj.Turbulence = 'LES'
obj.TurbulenceModel = 'kEqn'
obj.gx = '0 mm/s^2'
obj.gy = '-9.8e+03 mm/s^2'
obj.gz = '0 mm/s^2'

FreeCAD.ActiveDocument.FluidProperties.Material = {'Name': 'Air', 'Description': 'Standard air properties at 20 Degrees Celsius and 1 atm', 'Density': '1.20 kg/m^3', 'DynamicViscosity': '1.80e-5 kg/m/s', 'MolarMass': '0.0289643897748887 kg/mol', 'Cp': '1004.703 J/kg/K', 'SutherlandConstant': '1.4579326545176254e-06 kg/m/s/K^0.5', 'SutherlandTemperature': '110.4 K'}

FreeCAD.ActiveDocument.CfdSolver.StartFrom = "latestTime"

from CfdOF.Solve import CfdFluidBoundary
CfdTools.getActiveAnalysis().addObject(CfdFluidBoundary.makeCfdFluidBoundary())

bc = FreeCAD.ActiveDocument.CfdFluidBoundary
bc.BoundaryType = 'constraint'
bc.BoundarySubType = 'symmetry'
bc.ThermalBoundaryType = 'fixedValue'
bc.VelocityIsCartesian = True
bc.Ux = '0.0 mm/s'
bc.Uy = '0.0 mm/s'
bc.Uz = '0.0 mm/s'
bc.VelocityMag = '0.0 mm/s'
bc.DirectionFace = ''
bc.ReverseNormal = False
bc.MassFlowRate = '0.0 kg/s'
bc.VolFlowRate = '0.0 mm^3/s'
bc.Pressure = '0.0 kg/(mm*s^2)'
bc.SlipRatio = '0.0'
bc.Temperature = '290.0 K'
bc.HeatFlux = '0.0 kg/s^3'
bc.HeatTransferCoeff = '0.0 kg/(s^3*K)'
bc.TurbulenceInletSpecification = 'intensityAndLengthScale'
bc.TurbulentKineticEnergy = '10000.0 mm^2/s^2'
bc.SpecificDissipationRate = '1 1/s'
bc.DissipationRate = '50000000.0 mm^2/s^3'
bc.NuTilda = '55000000.0 mm^2/s'
bc.Intermittency = '1.0'
bc.ReThetat = '1.0'
bc.TurbulentViscosity = '50000000.0 mm^2/s'
bc.kEqnTurbulentKineticEnergy = '10000.0 mm^2/s^2'
bc.kEqnTurbulentViscosity = '50000000.0 mm^2/s'
bc.TurbulenceIntensityPercentage = '10'
bc.TurbulenceLengthScale = '100.0 mm'
bc.VolumeFractions = {}
bc.PorousBaffleMethod = 'porousCoeff'
bc.PressureDropCoeff = '0.0'
bc.ScreenWireDiameter = '0.2 mm'
bc.ScreenSpacing = '2.0 mm'
FreeCAD.ActiveDocument.CfdFluidBoundary.Label = 'constraint'
FreeCAD.ActiveDocument.CfdFluidBoundary.ShapeRefs = [
(FreeCAD.ActiveDocument.getObject('Pad'), ('Face8', 'Face7'))]
bc.DefaultBoundary = False
FreeCAD.ActiveDocument.recompute()

CfdTools.getActiveAnalysis().addObject(CfdFluidBoundary.makeCfdFluidBoundary())

bc = FreeCAD.ActiveDocument.CfdFluidBoundary001
bc.BoundaryType = 'constraint'
bc.BoundarySubType = 'symmetry'
bc.ThermalBoundaryType = 'fixedValue'
bc.VelocityIsCartesian = True
bc.Ux = '0.0 mm/s'
bc.Uy = '0.0 mm/s'
bc.Uz = '0.0 mm/s'
bc.VelocityMag = '0.0 mm/s'
bc.DirectionFace = ''
bc.ReverseNormal = False
bc.MassFlowRate = '0.0 kg/s'
bc.VolFlowRate = '0.0 mm^3/s'
bc.Pressure = '0.0 kg/(mm*s^2)'
bc.SlipRatio = '0.0'
bc.Temperature = '290.0 K'
bc.HeatFlux = '0.0 kg/s^3'
bc.HeatTransferCoeff = '0.0 kg/(s^3*K)'
bc.TurbulenceInletSpecification = 'intensityAndLengthScale'
bc.TurbulentKineticEnergy = '10000.0 mm^2/s^2'
bc.SpecificDissipationRate = '1 1/s'
bc.DissipationRate = '50000000.0 mm^2/s^3'
bc.NuTilda = '55000000.0 mm^2/s'
bc.Intermittency = '1.0'
bc.ReThetat = '1.0'
bc.TurbulentViscosity = '50000000.0 mm^2/s'
bc.kEqnTurbulentKineticEnergy = '10000.0 mm^2/s^2'
bc.kEqnTurbulentViscosity = '50000000.0 mm^2/s'
bc.TurbulenceIntensityPercentage = '10'
bc.TurbulenceLengthScale = '100.0 mm'
bc.VolumeFractions = {}
bc.PorousBaffleMethod = 'porousCoeff'
bc.PressureDropCoeff = '0.0'
bc.ScreenWireDiameter = '0.2 mm'
bc.ScreenSpacing = '2.0 mm'
FreeCAD.ActiveDocument.CfdFluidBoundary001.Label = 'wall'
FreeCAD.ActiveDocument.CfdFluidBoundary001.ShapeRefs = [
(FreeCAD.ActiveDocument.getObject('Pad'), ('Face6',))]
bc.DefaultBoundary = False
FreeCAD.ActiveDocument.recompute()

CfdTools.getActiveAnalysis().addObject(CfdFluidBoundary.makeCfdFluidBoundary())

bc = FreeCAD.ActiveDocument.CfdFluidBoundary002
bc.BoundaryType = 'wall'
bc.BoundarySubType = 'fixedWall'
bc.ThermalBoundaryType = 'fixedValue'
bc.VelocityIsCartesian = True
bc.Ux = '0.0 mm/s'
bc.Uy = '0.0 mm/s'
bc.Uz = '0.0 mm/s'
bc.VelocityMag = '0.0 mm/s'
bc.DirectionFace = ''
bc.ReverseNormal = False
bc.MassFlowRate = '0.0 kg/s'
bc.VolFlowRate = '0.0 mm^3/s'
bc.Pressure = '0.0 kg/(mm*s^2)'
bc.SlipRatio = '0.0'
bc.Temperature = '290.0 K'
bc.HeatFlux = '0.0 kg/s^3'
bc.HeatTransferCoeff = '0.0 kg/(s^3*K)'
bc.TurbulenceInletSpecification = 'intensityAndLengthScale'
bc.TurbulentKineticEnergy = '10000.0 mm^2/s^2'
bc.SpecificDissipationRate = '1 1/s'
bc.DissipationRate = '50000000.0 mm^2/s^3'
bc.NuTilda = '55000000.0 mm^2/s'
bc.Intermittency = '1.0'
bc.ReThetat = '1.0'
bc.TurbulentViscosity = '50000000.0 mm^2/s'
bc.kEqnTurbulentKineticEnergy = '10000.0 mm^2/s^2'
bc.kEqnTurbulentViscosity = '50000000.0 mm^2/s'
bc.TurbulenceIntensityPercentage = '10'
bc.TurbulenceLengthScale = '100.0 mm'
bc.VolumeFractions = {}
bc.PorousBaffleMethod = 'porousCoeff'
bc.PressureDropCoeff = '0.0'
bc.ScreenWireDiameter = '0.2 mm'
bc.ScreenSpacing = '2.0 mm'
FreeCAD.ActiveDocument.CfdFluidBoundary002.Label = 'wall001'
FreeCAD.ActiveDocument.CfdFluidBoundary002.ShapeRefs = [
(FreeCAD.ActiveDocument.getObject('Pad'), ('Face4', 'Face2', 'Face3'))]
bc.DefaultBoundary = False
FreeCAD.ActiveDocument.recompute()

CfdTools.getActiveAnalysis().addObject(CfdFluidBoundary.makeCfdFluidBoundary())

bc = FreeCAD.ActiveDocument.CfdFluidBoundary003
bc.BoundaryType = 'inlet'
bc.BoundarySubType = 'uniformVelocityInlet'
bc.ThermalBoundaryType = 'fixedValue'
bc.VelocityIsCartesian = True
bc.Ux = '20.0 mm/s'
bc.Uy = '0.0 mm/s'
bc.Uz = '0.0 mm/s'
bc.VelocityMag = '0.0 mm/s'
bc.DirectionFace = ''
bc.ReverseNormal = True
bc.MassFlowRate = '0.0 kg/s'
bc.VolFlowRate = '0.0 mm^3/s'
bc.Pressure = '0.0 kg/(mm*s^2)'
bc.SlipRatio = '0.0'
bc.Temperature = '290.0 K'
bc.HeatFlux = '0.0 kg/s^3'
bc.HeatTransferCoeff = '0.0 kg/(s^3*K)'
bc.TurbulenceInletSpecification = 'intensityAndLengthScale'
bc.TurbulentKineticEnergy = '10000.0 mm^2/s^2'
bc.SpecificDissipationRate = '1 1/s'
bc.DissipationRate = '50000000.0 mm^2/s^3'
bc.NuTilda = '55000000.0 mm^2/s'
bc.Intermittency = '1.0'
bc.ReThetat = '1.0'
bc.TurbulentViscosity = '50000000.0 mm^2/s'
bc.kEqnTurbulentKineticEnergy = '10000.0 mm^2/s^2'
bc.kEqnTurbulentViscosity = '50000000.0 mm^2/s'
bc.TurbulenceIntensityPercentage = '10'
bc.TurbulenceLengthScale = '100.0 mm'
bc.VolumeFractions = {}
bc.PorousBaffleMethod = 'porousCoeff'
bc.PressureDropCoeff = '0.0'
bc.ScreenWireDiameter = '0.2 mm'
bc.ScreenSpacing = '2.0 mm'
FreeCAD.ActiveDocument.CfdFluidBoundary003.Label = 'inlet'
FreeCAD.ActiveDocument.CfdFluidBoundary003.ShapeRefs = [
(FreeCAD.ActiveDocument.getObject('Pad'), ('Face1',))]
bc.DefaultBoundary = False
FreeCAD.ActiveDocument.recompute()

CfdTools.getActiveAnalysis().addObject(CfdFluidBoundary.makeCfdFluidBoundary())

bc = FreeCAD.ActiveDocument.CfdFluidBoundary004
bc.BoundaryType = 'outlet'
bc.BoundarySubType = 'staticPressureOutlet'
bc.ThermalBoundaryType = 'fixedValue'
bc.VelocityIsCartesian = True
bc.Ux = '0.0 mm/s'
bc.Uy = '0.0 mm/s'
bc.Uz = '0.0 mm/s'
bc.VelocityMag = '0.0 mm/s'
bc.DirectionFace = ''
bc.ReverseNormal = False
bc.MassFlowRate = '0.0 kg/s'
bc.VolFlowRate = '0.0 mm^3/s'
bc.Pressure = '0.0 kg/(mm*s^2)'
bc.SlipRatio = '0.0'
bc.Temperature = '290.0 K'
bc.HeatFlux = '0.0 kg/s^3'
bc.HeatTransferCoeff = '0.0 kg/(s^3*K)'
bc.TurbulenceInletSpecification = 'intensityAndLengthScale'
bc.TurbulentKineticEnergy = '10000.0 mm^2/s^2'
bc.SpecificDissipationRate = '1 1/s'
bc.DissipationRate = '50000000.0 mm^2/s^3'
bc.NuTilda = '55000000.0 mm^2/s'
bc.Intermittency = '1.0'
bc.ReThetat = '1.0'
bc.TurbulentViscosity = '50000000.0 mm^2/s'
bc.kEqnTurbulentKineticEnergy = '10000.0 mm^2/s^2'
bc.kEqnTurbulentViscosity = '50000000.0 mm^2/s'
bc.TurbulenceIntensityPercentage = '10'
bc.TurbulenceLengthScale = '100.0 mm'
bc.VolumeFractions = {}
bc.PorousBaffleMethod = 'porousCoeff'
bc.PressureDropCoeff = '0.0'
bc.ScreenWireDiameter = '0.2 mm'
bc.ScreenSpacing = '2.0 mm'
FreeCAD.ActiveDocument.CfdFluidBoundary004.Label = 'outlet'
FreeCAD.ActiveDocument.CfdFluidBoundary004.ShapeRefs = [(FreeCAD.ActiveDocument.getObject('Pad'), ('Face5',))]
bc.DefaultBoundary = False
FreeCAD.ActiveDocument.recompute()

bc = FreeCAD.ActiveDocument.CfdFluidBoundary003
bc.BoundaryType = 'inlet'
bc.BoundarySubType = 'uniformVelocityInlet'
bc.ThermalBoundaryType = 'fixedValue'
bc.VelocityIsCartesian = True
bc.Ux = '10.0 mm/s'
bc.Uy = '0.0 mm/s'
bc.Uz = '0.0 mm/s'
bc.VelocityMag = '0.0 mm/s'
bc.DirectionFace = ''
bc.ReverseNormal = True
bc.MassFlowRate = '0.0 kg/s'
bc.VolFlowRate = '0.0 mm^3/s'
bc.Pressure = '0.0 kg/(mm*s^2)'
bc.SlipRatio = '0.0'
bc.Temperature = '290.0 K'
bc.HeatFlux = '0.0 kg/s^3'
bc.HeatTransferCoeff = '0.0 kg/(s^3*K)'
bc.TurbulenceInletSpecification = 'TurbulentViscosityAndK'
bc.TurbulentKineticEnergy = '150000.0 mm^2/s^2'
bc.SpecificDissipationRate = '1 1/s'
bc.DissipationRate = '50000000.0 mm^2/s^3'
bc.NuTilda = '55000000.0 mm^2/s'
bc.Intermittency = '1.0'
bc.ReThetat = '1.0'
bc.TurbulentViscosity = '50000000.0 mm^2/s'
bc.kEqnTurbulentKineticEnergy = '150000.0 mm^2/s^2'
bc.kEqnTurbulentViscosity = '50000000.0 mm^2/s'
bc.TurbulenceIntensityPercentage = '10'
bc.TurbulenceLengthScale = '100.0 mm'
bc.VolumeFractions = {}
bc.PorousBaffleMethod = 'porousCoeff'
bc.PressureDropCoeff = '0.0'
bc.ScreenWireDiameter = '0.2 mm'
bc.ScreenSpacing = '2.0 mm'
FreeCAD.ActiveDocument.CfdFluidBoundary003.Label = 'inlet'
FreeCAD.ActiveDocument.CfdFluidBoundary003.ShapeRefs = [
(FreeCAD.ActiveDocument.getObject('Pad'), ('Face1',))]
bc.DefaultBoundary = False
FreeCAD.ActiveDocument.recompute()

init = FreeCAD.ActiveDocument.InitialiseFields
init.PotentialFlow = False
init.UseInletUValues = False
init.Ux = '0.0 mm/s'
init.Uy = '0.0 mm/s'
init.Uz = '0.0 mm/s'
init.UseOutletPValue = True
init.PotentialFlowP = False
init.Pressure = '0.0 kg/(mm*s^2)'
init.VolumeFractions = {}
init.UseInletTemperatureValue = False
init.Temperature = '290.0 K'
init.UseInletTurbulenceValues = False
init.k = '10000.0 mm^2/s^2'
init.epsilon = '50000000.0 mm^2/s^3'
init.omega = '1 1/s'
init.nuTilda = '55000000.0 mm^2/s'
init.gammaInt = '1.0'
init.ReThetat = '1.0'
init.nut = '50000000.0 mm^2/s'
init.k = '0.0 mm^2/s^2'
init.nut = '0.0 mm^2/s'
init.BoundaryU = FreeCAD.ActiveDocument.CfdFluidBoundary003
init.BoundaryP = FreeCAD.ActiveDocument.CfdFluidBoundary004
init.BoundaryT = FreeCAD.ActiveDocument.CfdFluidBoundary003
init.BoundaryTurb = FreeCAD.ActiveDocument.CfdFluidBoundary003
