import Draft
Gui.activateWorkbench("DraftWorkbench")
pl = App.Placement(App.Vector(250,0,0),App.Rotation(App.Vector(0,1,0),-45))
rec = Draft.makeRectangle(length=87,height=100,placement=pl,face=True,support=None)
Draft.autogroup(rec)
FreeCAD.ActiveDocument.recompute()

Gui.activateWorkbench("CfdOFWorkbench")

from CfdOF.Mesh import CfdMeshRefinement
CfdMeshRefinement.makeCfdMeshRefinement(App.ActiveDocument.Fusion_Mesh)
FreeCAD.ActiveDocument.MeshRefinement.RelativeLength = 0.5
FreeCAD.ActiveDocument.MeshRefinement.RefinementThickness = '0 mm'
FreeCAD.ActiveDocument.MeshRefinement.NumberLayers = 0
FreeCAD.ActiveDocument.MeshRefinement.ExpansionRatio = 1.2
FreeCAD.ActiveDocument.MeshRefinement.FirstLayerHeight = '0 mm'
FreeCAD.ActiveDocument.MeshRefinement.RegionEdgeRefinement = 1.0
FreeCAD.ActiveDocument.MeshRefinement.Internal = False
FreeCAD.ActiveDocument.MeshRefinement.ShapeRefs = [(FreeCAD.ActiveDocument.getObject('Rectangle'), ('Face1'))]
FreeCAD.ActiveDocument.recompute()

from CfdOF.Solve import CfdFluidBoundary
from CfdOF import CfdTools
CfdTools.getActiveAnalysis().addObject(CfdFluidBoundary.makeCfdFluidBoundary())

bc = FreeCAD.ActiveDocument.CfdFluidBoundary003
bc.BoundaryType = 'baffle'
bc.BoundarySubType = 'porousBaffle'
bc.ThermalBoundaryType = 'fixedValue'
bc.PorousBaffleMethod = 'porousCoeff'
bc.PressureDropCoeff = '0.84 '
bc.ScreenWireDiameter = '0.1 mm'
bc.ScreenSpacing = '0 mm'
FreeCAD.ActiveDocument.CfdFluidBoundary003.Label = 'baffle'
FreeCAD.ActiveDocument.CfdFluidBoundary003.ShapeRefs = [(FreeCAD.ActiveDocument.getObject('Rectangle'), ('Face1'))]
FreeCAD.ActiveDocument.recompute()
