doc = App.newDocument()
Gui.activateWorkbench("PartWorkbench")
import PartDesignGui
App.ActiveDocument.addObject("Part::Box","Box")
App.ActiveDocument.ActiveObject.Label = "Cube"
App.ActiveDocument.recompute()
App.ActiveDocument.addObject("Part::Box","Box")
App.ActiveDocument.ActiveObject.Label = "Cube"
App.ActiveDocument.recompute()
Gui.SendMsgToActiveView("ViewFit")
App.ActiveDocument.getObject("Box").Width = '100 mm'
App.ActiveDocument.getObject("Box").Height = '300 mm'
App.ActiveDocument.getObject("Box").Length = '100 mm'
App.ActiveDocument.getObject("Box001").Width = '100 mm'
App.ActiveDocument.getObject("Box001").Height = '100 mm'
App.ActiveDocument.getObject("Box001").Length = '600 mm'
App.activeDocument().addObject("Part::MultiFuse","Fusion0")
App.activeDocument().Fusion0.Shapes = [App.activeDocument().Box,App.activeDocument().Box001,]

App.ActiveDocument.addObject('Part::Refine','Fusion')
App.ActiveDocument.Fusion.Source = App.ActiveDocument.getObject('Fusion0')
App.ActiveDocument.getObject('Fusion0').Visibility = False

FreeCAD.ActiveDocument.recompute()
Gui.activeDocument().activeView().viewDimetric()
Gui.SendMsgToActiveView("ViewFit")
