import FreeCAD
import PartDesignGui
import os

# Gui.runCommand('Std_DlgMacroRecord',0)
### Begin command Std_Open
FreeCAD.openDocument(os.path.join(os.path.dirname(__file__), "PeriodicBoundaryMeanVelocityForce.FCStd"))
# App.setActiveDocument("PeriodicBoundaryMeanVelocityForce")
# App.ActiveDocument=App.getDocument("PeriodicBoundaryMeanVelocityForce")
# Gui.ActiveDocument=Gui.getDocument("PeriodicBoundaryMeanVelocityForce")
### End command Std_Open
App.ActiveDocument.recompute()
