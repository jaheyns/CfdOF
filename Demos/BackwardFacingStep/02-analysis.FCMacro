# create the analysis
from CfdOF import CfdAnalysis
from CfdOF import CfdTools
analysis = CfdAnalysis.makeCfdAnalysis('CfdAnalysis')
CfdTools.setActiveAnalysis(analysis)
from CfdOF.Solve import CfdPhysicsSelection
analysis.addObject(CfdPhysicsSelection.makeCfdPhysicsSelection())
from CfdOF.Solve import CfdFluidMaterial
analysis.addObject(CfdFluidMaterial.makeCfdFluidMaterial('FluidProperties'))
from CfdOF.Solve import CfdInitialiseFlowField
analysis.addObject(CfdInitialiseFlowField.makeCfdInitialFlowField())
from CfdOF.Solve import CfdSolverFoam
analysis.addObject(CfdSolverFoam.makeCfdSolverFoam())
App.ActiveDocument.PhysicsModel.Time = 'Transient'
App.ActiveDocument.PhysicsModel.Turbulence = 'LES'
App.ActiveDocument.PhysicsModel.TurbulenceModel = 'kEqn'
App.ActiveDocument.InitialiseFields.PotentialFlow = False
App.ActiveDocument.InitialiseFields.UseOutletPValue = True
App.ActiveDocument.InitialiseFields.Ux = '0.0 mm/s'
App.ActiveDocument.InitialiseFields.Uy = '0.0 mm/s'
App.ActiveDocument.InitialiseFields.Uz = '0.0 mm/s'
App.ActiveDocument.InitialiseFields.k = '0.0 mm^2/s^2'
App.ActiveDocument.InitialiseFields.nut = '0.0 mm^2/s'
App.activeDocument().recompute(None,True,True)
