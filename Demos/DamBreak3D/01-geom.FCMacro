import FreeCAD
import Part

App.newDocument()

# make the tank box
App.ActiveDocument.addObject("Part::Box","Box")
App.ActiveDocument.ActiveObject.Label = "tank"
App.ActiveDocument.recompute()
App.ActiveDocument.Box.Length = '3220 mm'
App.ActiveDocument.Box.Width = '1000 mm'
App.ActiveDocument.Box.Height = '1000 mm'

# make the tank box
App.ActiveDocument.addObject("Part::Box","Box")
App.ActiveDocument.ActiveObject.Label = "obstacle"
App.ActiveDocument.recompute()
App.ActiveDocument.Box001.Length = '160 mm'
App.ActiveDocument.Box001.Width = '400 mm'
App.ActiveDocument.Box001.Height = '160 mm'
App.ActiveDocument.Box001.Placement = App.Placement(App.Vector(670,300,0),App.Rotation(App.Vector(0,0,1),0))

# make the fluid domain
from BOPTools import BOPFeatures
bp = BOPFeatures.BOPFeatures(App.activeDocument())
bp.make_cut(["Box", "Box001", ])
App.ActiveDocument.Cut.Label = "fluid_domain"
App.ActiveDocument.recompute()

# make the initial water volume
App.ActiveDocument.addObject("Part::Box","Box")
App.ActiveDocument.ActiveObject.Label = "initWater"
App.ActiveDocument.Box002.Length = '1220 mm'
App.ActiveDocument.Box002.Width = '1000 mm'
App.ActiveDocument.Box002.Height = '550 mm'
App.ActiveDocument.Box002.Placement = App.Placement(App.Vector(2000,0,0),App.Rotation(App.Vector(0,0,1),0))
App.ActiveDocument.recompute()
