# make the water zone
from CfdOF.Solve import CfdZone
from CfdOF import CfdTools
CfdTools.getActiveAnalysis().addObject(CfdZone.makeCfdInitialisationZone())
App.ActiveDocument.InitialisationZone.VolumeFractions = {'water': '1.0'}
FreeCAD.ActiveDocument.InitialisationZone.ShapeRefs = [
(FreeCAD.ActiveDocument.Box002, ('Solid1',))]
App.activeDocument().recompute(None,True,True)
