# -*- coding: utf-8 -*-

import FreeCAD

# Gui.runCommand('Std_DlgMacroRecord',0)
### Begin command Std_Workbench
# Gui.activateWorkbench("CfdOFWorkbench")
### End command Std_Workbench
### Begin command CfdOF_ReportingFunctions
from CfdOF.PostProcess import CfdReportingFunction
from CfdOF import CfdTools
CfdTools.getActiveAnalysis().addObject(CfdReportingFunction.makeCfdReportingFunction())
### End command CfdOF_ReportingFunctions
App.ActiveDocument.ReportingFunction.ReportingFunctionType = 'Probes'
FreeCAD.ActiveDocument.ReportingFunction.Patch = FreeCAD.ActiveDocument.CfdFluidBoundary
App.ActiveDocument.ReportingFunction.ProbePosition = App.Vector (830.0, 474.0, 99.0)
App.ActiveDocument.ReportingFunction.Label = 'P3'
FreeCAD.ActiveDocument.recompute()
# Gui.Selection.addSelection('Unnamed','ReportingFunction')
### Begin command CfdOF_ReportingFunctions
from CfdOF.PostProcess import CfdReportingFunction
from CfdOF import CfdTools
CfdTools.getActiveAnalysis().addObject(CfdReportingFunction.makeCfdReportingFunction())
### End command CfdOF_ReportingFunctions
App.ActiveDocument.ReportingFunction001.ReportingFunctionType = 'Probes'
FreeCAD.ActiveDocument.ReportingFunction001.Patch = FreeCAD.ActiveDocument.CfdFluidBoundary
App.ActiveDocument.ReportingFunction001.ProbePosition = App.Vector (733.0, 526.0, 160.0)
App.ActiveDocument.ReportingFunction001.Label = 'P7'
FreeCAD.ActiveDocument.recompute()
# Gui.Selection.clearSelection()
# Gui.Selection.addSelection('Unnamed','ReportingFunction001')
