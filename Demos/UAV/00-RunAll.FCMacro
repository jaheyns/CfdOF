from os import path
from CfdOF.CfdTools import executeMacro
dir = path.dirname(__file__)
executeMacro(path.join(dir, '01-partDesign.FCMacro'))
executeMacro(path.join(dir, '02-firstAnalysis.FCMacro'))
executeMacro(path.join(dir, '03-refineMesh.FCMacro'))
executeMacro(path.join(dir, '04-forces.FCMacro'))
