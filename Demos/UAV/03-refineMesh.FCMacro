Gui.activateWorkbench("PartWorkbench")
App.ActiveDocument.addObject("Part::Sphere","Sphere")
App.ActiveDocument.ActiveObject.Label = "Sphere"
FreeCAD.ActiveDocument.getObject("Sphere").Placement = App.Placement(App.Vector(0,100,-350),App.Rotation(App.Vector(0,0,1),0))
FreeCAD.ActiveDocument.getObject("Sphere").Radius = '800 mm'
App.ActiveDocument.recompute()

Gui.activateWorkbench("CfdOFWorkbench")

from CfdOF.Mesh import CfdMeshRefinement
CfdMeshRefinement.makeCfdMeshRefinement(App.ActiveDocument.Compound001_Mesh)
FreeCAD.ActiveDocument.MeshRefinement001.ShapeRefs = [
(FreeCAD.ActiveDocument.getObject('Sphere'), ('Solid1'))]

FreeCAD.ActiveDocument.MeshRefinement001.RelativeLength = 0.25
FreeCAD.ActiveDocument.MeshRefinement001.RefinementThickness = '0 mm'
FreeCAD.ActiveDocument.MeshRefinement001.NumberLayers = 0
FreeCAD.ActiveDocument.MeshRefinement001.ExpansionRatio = 1.2
FreeCAD.ActiveDocument.MeshRefinement001.FirstLayerHeight = '0 mm'
FreeCAD.ActiveDocument.MeshRefinement001.RegionEdgeRefinement = 1.0
FreeCAD.ActiveDocument.MeshRefinement001.Internal = True

FreeCAD.ActiveDocument.MeshRefinement.RelativeLength = 0.02
FreeCAD.ActiveDocument.MeshRefinement.RefinementThickness = '1 mm'
FreeCAD.ActiveDocument.MeshRefinement.NumberLayers = 3
FreeCAD.ActiveDocument.MeshRefinement.ExpansionRatio = 1.2
FreeCAD.ActiveDocument.MeshRefinement.FirstLayerHeight = '0 mm'
FreeCAD.ActiveDocument.MeshRefinement.RegionEdgeRefinement = 1
FreeCAD.ActiveDocument.MeshRefinement.Internal = False

# Front wheel 
CfdMeshRefinement.makeCfdMeshRefinement(App.ActiveDocument.Compound001_Mesh)
FreeCAD.ActiveDocument.MeshRefinement002.ShapeRefs = [
(FreeCAD.ActiveDocument.getObject('Compound'), (
'Face37','Face38','Face39','Face40','Face41','Face42','Face43','Face44','Face45','Face46','Face47','Face48',
'Face49','Face50','Face51','Face52','Face53','Face54','Face55','Face56','Face57','Face58','Face83','Face84',
'Face85','Face86','Face87','Face88','Face89','Face90','Face91','Face92','Face93','Face94','Face95','Face96'))] 
FreeCAD.ActiveDocument.MeshRefinement002.RelativeLength = 0.02
FreeCAD.ActiveDocument.MeshRefinement002.RefinementThickness = '1 mm'
FreeCAD.ActiveDocument.MeshRefinement002.NumberLayers = 0
FreeCAD.ActiveDocument.MeshRefinement002.ExpansionRatio = 1.2
FreeCAD.ActiveDocument.MeshRefinement002.FirstLayerHeight = '0 mm'
FreeCAD.ActiveDocument.MeshRefinement002.RegionEdgeRefinement = 1.0
FreeCAD.ActiveDocument.MeshRefinement002.Internal = False

FreeCADGui.ActiveDocument.Sphere.Transparency = 50
