import FreeCAD
import PartDesignGui
import os

# Gui.runCommand('Std_DlgMacroRecord',0)
### Begin command Std_Open
FreeCAD.openDocument(os.path.join(os.path.dirname(__file__), "PeriodicBoundaryAndMeanVelocityForce.FCStd"))
# App.setActiveDocument("PeriodicBoundaryAndMeanVelocityForce")
# App.ActiveDocument=App.getDocument("PeriodicBoundaryAndMeanVelocityForce")
# Gui.ActiveDocument=Gui.getDocument("PeriodicBoundaryAndMeanVelocityForce")
### End command Std_Open
App.ActiveDocument.recompute()
