import FreeCAD
import CfdImportSTL
import Part
import os

CfdImportSTL.open(os.path.join(os.path.dirname(__file__), "modifiedFinner.stl"))
App.ActiveDocument.addObject("Part::Feature","body001")
__shape__=Part.Shape()
__shape__.makeShapeFromMesh(App.ActiveDocument.getObject("body").Mesh.Topology,0.001000)
App.ActiveDocument.getObject("body001").Shape=__shape__
App.ActiveDocument.getObject("body001").purgeTouched()
del __shape__

App.ActiveDocument.addObject('Part::Refine','body001').Source=App.ActiveDocument.body001
App.ActiveDocument.ActiveObject.Label=App.ActiveDocument.body001.Label
Gui.ActiveDocument.body001.hide()

App.ActiveDocument.recompute()
Gui.SendMsgToActiveView("ViewFit")

App.ActiveDocument.addObject("Part::Feature","fin1001")
__shape__=Part.Shape()
__shape__.makeShapeFromMesh(FreeCAD.getDocument("modifiedFinner").getObject("fin1").Mesh.Topology,0.001000)
App.ActiveDocument.getObject("fin1001").Shape=__shape__
App.ActiveDocument.getObject("fin1001").purgeTouched()
del __shape__

App.ActiveDocument.addObject('Part::Refine','fin1001').Source=App.ActiveDocument.fin1001
App.ActiveDocument.ActiveObject.Label=App.ActiveDocument.fin1001.Label
Gui.ActiveDocument.fin1001.hide()

App.ActiveDocument.recompute()

App.ActiveDocument.addObject("Part::Feature","fin2001")
__shape__=Part.Shape()
__shape__.makeShapeFromMesh(App.ActiveDocument.getObject("fin2").Mesh.Topology,0.001000)
App.ActiveDocument.getObject("fin2001").Shape=__shape__
App.ActiveDocument.getObject("fin2001").purgeTouched()
del __shape__

App.ActiveDocument.addObject('Part::Refine','fin2001').Source=App.ActiveDocument.fin2001
App.ActiveDocument.ActiveObject.Label=App.ActiveDocument.fin2001.Label
Gui.ActiveDocument.fin2001.hide()

App.ActiveDocument.recompute()

App.ActiveDocument.addObject("Part::Feature","fin3001")
__shape__=Part.Shape()
__shape__.makeShapeFromMesh(App.ActiveDocument.getObject("fin3").Mesh.Topology,0.001000)
App.ActiveDocument.getObject("fin3001").Shape=__shape__
App.ActiveDocument.getObject("fin3001").purgeTouched()
del __shape__
App.ActiveDocument.addObject('Part::Refine','fin3001').Source=App.ActiveDocument.fin3001
App.ActiveDocument.ActiveObject.Label=App.ActiveDocument.fin3001.Label
Gui.ActiveDocument.fin3001.hide()

App.ActiveDocument.recompute()
App.ActiveDocument.addObject("Part::Feature","fin4001")
__shape__=Part.Shape()
__shape__.makeShapeFromMesh(App.ActiveDocument.getObject("fin4").Mesh.Topology,0.001000)
App.ActiveDocument.getObject("fin4001").Shape=__shape__
App.ActiveDocument.getObject("fin4001").purgeTouched()
del __shape__

App.ActiveDocument.addObject('Part::Refine','fin4001').Source=App.ActiveDocument.fin4001
App.ActiveDocument.ActiveObject.Label=App.ActiveDocument.fin4001.Label
Gui.ActiveDocument.fin4001.hide()

App.ActiveDocument.recompute()

App.ActiveDocument.removeObject('body')
App.ActiveDocument.removeObject('fin1')
App.ActiveDocument.removeObject('fin2')
App.ActiveDocument.removeObject('fin3')
App.ActiveDocument.removeObject('fin4')
App.ActiveDocument.recompute()

App.activeDocument().addObject("Part::Compound","Compound")
App.activeDocument().Compound.Links = [App.activeDocument().body001001,App.activeDocument().fin1001001,App.activeDocument().fin2001001,App.activeDocument().fin3001001,App.activeDocument().fin4001001,]
App.ActiveDocument.recompute()

App.ActiveDocument.addObject("Part::Box","Box")
App.ActiveDocument.ActiveObject.Label = "Cube"

App.ActiveDocument.getObject('Box').Length = '2000 mm'
App.ActiveDocument.getObject('Box').Width = '2000 mm'
App.ActiveDocument.getObject('Box').Height = '2000 mm'
Gui.ActiveDocument.getObject('Box').Transparency = 50
App.ActiveDocument.getObject('Box').Placement = App.Placement(App.Vector(-1200,-1000,-1000),App.Rotation(App.Vector(0,0,1),0))

Gui.activeDocument().activeView().viewTrimetric()
App.ActiveDocument.recompute()

App.activeDocument().addObject("Part::Compound","Compound")
App.activeDocument().Compound001.Links = [App.activeDocument().Box,App.activeDocument().Compound,]
App.ActiveDocument.recompute()
